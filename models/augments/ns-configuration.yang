/*
  Copyright 2020 Whitestack LLC

  Licensed under the Apache License, Version 2.0 (the "License");
  you may not use this file except in compliance with the License.
  You may obtain a copy of the License at

    http://www.apache.org/licenses/LICENSE-2.0

  Unless required by applicable law or agreed to in writing, software
  distributed under the License is distributed on an "AS IS" BASIS,
  WITHOUT WARRANTIES OR CONDITIONS OF ANY KIND, either express or
  implied.
  See the License for the specific language governing permissions and
  limitations under the License.
*/

module ns-configuration {
    yang-version 1.1;
    namespace "urn:etsi:osm:yang:augments:ns-configuration";
    prefix "ns-configuration";

    import etsi-nfv-nsd {
        prefix nsd;
    }

    import common-augments {
        prefix common;
    }

    grouping extended-ns-configuration {
        container ns-configuration {
            description
              "Information about NS configuration.";

            uses common:vnfc-configuration;
            uses common:vnfc-relations;
        }
    }

    augment "/nsd:nsd/nsd:nsd" {
        uses extended-ns-configuration;
    }
}
