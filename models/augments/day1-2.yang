/*
  Copyright 2020 Whitestack LLC

  Licensed under the Apache License, Version 2.0 (the "License");
  you may not use this file except in compliance with the License.
  You may obtain a copy of the License at

    http://www.apache.org/licenses/LICENSE-2.0

  Unless required by applicable law or agreed to in writing, software
  distributed under the License is distributed on an "AS IS" BASIS,
  WITHOUT WARRANTIES OR CONDITIONS OF ANY KIND, either express or
  implied.
  See the License for the specific language governing permissions and
  limitations under the License.
*/

module day1-2 {
    yang-version 1.1;
    namespace "urn:etsi:osm:yang:augments:day1-2";
    prefix "day1-2";

    import etsi-nfv-vnfd {
        prefix vnfd;
    }

    import common-augments {
        prefix common;
    }

    grouping extended-vnf-configuration {
        list day1-2 {
            key "id";
            leaf id {
                description
                  "Internal identifier for the VNF/VDU/KNF/KDU configuration";
                type string;
            }
            uses common:vnfc-configuration;
            uses common:relations;
            uses common:vdu-config-access;

            leaf-list blacklist-config-primitive {
                description
                  "List of blacklisted config primitives from the list of
                   default kdu config primitives";

                type enumeration {
                    enum upgrade;
                    enum rollback;
                }
            }
        }
    }

    augment "/vnfd:vnfd/vnfd:df/vnfd:lcm-operations-configuration/vnfd:operate-vnf-op-config" {
        uses extended-vnf-configuration;
    }
}
