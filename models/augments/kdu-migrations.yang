module kdu-migrations {
  yang-version 1.1;
  namespace "urn:etsi:osm:yang:augments:kdu-migrations";
  prefix "kdu-migrations";

  import etsi-nfv-vnfd {
    prefix vnfd;
  }

  import common-augments {
    prefix common;
  }

  import scaling {
    prefix scaling;
  }

  grouping migration-descriptor {
    list migration-aspect {
      
      key "id";

      leaf id {
        description
          "Unique identifier of this aspect in the VNFD.";
        type string;
      }

      leaf name {
        description 
          "Human readable name of the aspect.";
        type string;
      }

      leaf description {
        description
          "Human readable description of the aspect.";
        type string;
      }

      list migration-policy {

        key "name";

        leaf name {
          description
            "Name of the migration policy";
          type string;
        }

        leaf enabled {
          description
            "Specifies if the migration policy can be applied";
          type boolean;
          default true;
        }

        leaf migration-criteria-operation {
          description 
            "Operation to be applied to check between migration criterias to
             check if the migration threshold condition has been met.
             Defaults to AND";
          type common:scaling-criteria-operation;
          default AND;
        }

        leaf threshold-time {
          description
            "The duration, in seconds, for which the criteria must hold true";
          type uint32;
          mandatory true;
        }

        leaf cooldown-time {
          description
            "The duration, in seconds, after a migration action has been
              triggered, for which there will be no other migrations";
          type decimal64 {
            fraction-digits 3;
          }
          mandatory true;
        }

        leaf kdu-resource-ref {
          description
            "Identifier of a KDU resource";
          type leafref {
            path "/vnfd:vnfd/vnfd:df/scaling:kdu-resource-profile/scaling:id";
          }
        }

        list migration-criteria {
          description 
            "list of conditions to be met for generating migration 
              requests";
          key "name";

          leaf name {
            type string;
          }

          leaf threshold {
            description
              "Value which migration requests are generated";
            type decimal64 {
              fraction-digits 5;
            }
            mandatory true;
          }

          leaf migration-relational-operation {
            description
              "The relational operator used to compare the monitoring
                param agaisnt the threshold value. Defaults to Greater or Equal";
            type common:relational-operation-type;
            default GE;
          }

          leaf vnf-monitoring-param-ref {
            description 
              "Reference to the VNF level a monitoring parameter
               that is aggregated";
            type string;
          }
        }
      }
    }
  }
  
  grouping extended-kdu-resource-profile {
    leaf-list node-blacklist {
      description
        "List of nodes this KDU is not allowed to be scheduled. 
        Shall be any label used to reference a single/multiple nodes";
      type string;
    }

    leaf-list node-list {
      description
        "List of nodes this KDU is allowed to be scheduled. 
        Shall be any label used to reference a single/multiple nodes";
      type string;
    }
  }

  augment "/vnfd:vnfd/vnfd:df/scaling:kdu-resource-profile" {
    uses extended-kdu-resource-profile;
  }

  augment "/vnfd:vnfd/vnfd:df" {
    uses migration-descriptor;
  }
}
